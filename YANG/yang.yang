module interfaces {

    yang-version "1.1";
    namespace "https://mysiteisisisis.com/interfaces";
    prefix "interfaces";

    typedef vlan-type {
        type uint16 {
            range 1..4096;
        }
        description "vlan data type";
    }

    container interfaces {
        list switchport_list {
            description "switchport interfaces";
            key "name";

            leaf name {
                type string;
            }
            leaf enabled {
                type boolean;
                default "false";
            }
            leaf vlan {
                type vlan-type;
                default 1;
            }
            leaf int_description {
                type string;
                default "description by yang";
            }
        }

        list virtual_interface_list {
            description "virtual interfaces";
            key "name";

            leaf name {
                type string;
            }
            leaf enabled {
                type boolean;
                default "false";
            }
            leaf ip_address {
                type string;
                default "0.0.0.0";
            }
            leaf int_description {
                type string;
                default "description by yang";
            }
        }
    }
}
